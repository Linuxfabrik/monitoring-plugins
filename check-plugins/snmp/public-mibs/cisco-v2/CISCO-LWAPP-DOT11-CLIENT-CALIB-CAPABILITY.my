-- *****************************************************************
-- CISCO-LWAPP-DOT11-CLIENT-CALIB-CAPABILITY.my:  
-- CISCO-LWAPP-DOT11-CLIENT-CALIB MIB CAPABILITIES
--
-- May 2006 -  Prasanna Viswakumar
--
-- Copyright (c) 2006 by cisco Systems, Inc.
-- All rights reserved.
--
-- *****************************************************************

CISCO-LWAPP-DOT11-CLIENT-CALIB-CAPABILITY DEFINITIONS ::= BEGIN

IMPORTS
        MODULE-IDENTITY
                FROM SNMPv2-SMI
        AGENT-CAPABILITIES
                FROM SNMPv2-CONF
        ciscoAgentCapability
                FROM CISCO-SMI;

ciscoLwappDot11ClientCalibCapability MODULE-IDENTITY  
        LAST-UPDATED         "200605160000Z"
        ORGANIZATION         "Cisco Systems, Inc."
        CONTACT-INFO
                "             Cisco Systems
                              Customer Service

                      Postal: 170 W Tasman Drive
                              San Jose, CA  95134
                              USA
  
                         Tel: +1 800 553-NETS
 
                      E-mail: cs-wnbu-snmp@cisco.com"
        DESCRIPTION
                "Agent capabilities for 
                 CISCO-LWAPP-DOT11-CLIENT-CALIB-MIB. "
        REVISION      "200605160000Z"
        DESCRIPTION
                "Initial version of this MIB module. "
        ::= { ciscoAgentCapability 502 }

ciscoLwappDot11ClientCalibCapabilityCUWNSV4R0 AGENT-CAPABILITIES
    
PRODUCT-RELEASE         "Cisco Unified Wireless Network Software
                        Release 4.0"
        STATUS          current
        DESCRIPTION     "CISCO-LWAPP-DOT11-CLIENT-CALIB-MIB
                         capabilities. "

        SUPPORTS        CISCO-LWAPP-DOT11-CLIENT-CALIB-MIB
        INCLUDES        {
                        ciscoLwappDot11ClientCalibMIBConfigGroup
                        }   

        VARIATION       cLD11ClientCalibTableMaxEntries
        ACCESS          read-only
        DESCRIPTION
                        "This object is implemented as
                        read-only. "
        ::= { ciscoLwappDot11ClientCalibCapability 1 }
END

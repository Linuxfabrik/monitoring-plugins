-- *****************************************************************
-- CISCO-OSPF-TRAP-CAPABILITY.my: OSPF TRAP MIB AGENT-CAPABILITIES
-- 
-- Oct 2002, Roy Jose
--
-- Copyright (c) 2002 by Cisco Systems, Inc.
-- All rights reserved.
-- 
-- *****************************************************************

CISCO-OSPF-TRAP-CAPABILITY DEFINITIONS ::= BEGIN

IMPORTS
    MODULE-IDENTITY
        FROM SNMPv2-SMI
    AGENT-CAPABILITIES
        FROM SNMPv2-CONF
    ciscoAgentCapability
        FROM CISCO-SMI;

ciscoOspfTrapCapability    MODULE-IDENTITY
        LAST-UPDATED    "200211240000Z"
        ORGANIZATION    "Cisco Systems, Inc."
        CONTACT-INFO
                      "Cisco Systems Customer Service
            
            Postal:    170 West Tasman Drive
                       San Jose, CA  95134,
                       USA

               Tel:    +1 800 553-NETS
            
            E-mail:    cs-ospf@cisco.com"
        DESCRIPTION
            "Agent capabilities for the OSPF TRAP MIB."
        REVISION "200211240000Z"
        DESCRIPTION
            "Initial version of the MIB Module"
    ::= { ciscoAgentCapability 288 }

ciscoOspfTrapCapabilityV12R026S AGENT-CAPABILITIES

PRODUCT-RELEASE "Cisco IOS 12.0(26)S"
STATUS          current
DESCRIPTION     "CISCO-OSPF-TRAP-MIB capabilites"

SUPPORTS        OSPF-TRAP-MIB
INCLUDES        { ospfTrapControlGroup }

VARIATION       ospfSetTrap
DESCRIPTION
                "A four-octet string serving as a bit  map  for
                the trap events defined by the OSPF traps. This
                object is used to enable and  disable  specific
                OSPF   traps   where  a  1  in  the  bit  field
                represents enabled.  The right-most bit  (least
                significant) represents trap 0. ospfLsdbOverflow
                and ospfLsdbApproachingOverflow are not supported"

VARIATION       ospfConfigErrorType
ACCESS          accessible-for-notify
DESCRIPTION     "This object is inaccessible except through OSPF
                 notification messages"

VARIATION       ospfPacketType
ACCESS          accessible-for-notify
DESCRIPTION     "This object is inaccessible except through OSPF
                 notification messages"

VARIATION       ospfPacketSrc
ACCESS          accessible-for-notify
DESCRIPTION     "This object is inaccessible except through OSPF
                 notification messages"

VARIATION       ospfLsdbOverflow
ACCESS          not-implemented
DESCRIPTION     "This object is not supported as there is no 
                 Lsdb limit in IOS"

VARIATION       ospfLsdbApproachingOverflow
ACCESS          not-implemented
DESCRIPTION     "This object is not supported as there is no 
                 Lsdb limit in IOS"

    ::= { ciscoOspfTrapCapability 1 }

END
</PRE></BODY></HTML>
